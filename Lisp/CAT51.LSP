(defun c:go()(command "rectangle" (list 0.000000 0.000000) (list 34.000000 6.000000))(command "rectangle" (list 34.000000 0.000000) (list 67.000000 14.000000))(command "rectangle" (list 67.000000 0.000000) (list 73.000000 5.000000))(command "rectangle" (list 73.000000 0.000000) (list 74.000000 4.000000))(command "rectangle" (list 74.000000 0.000000) (list 89.000000 25.000000))(command "rectangle" (list 0.000000 6.000000) (list 16.000000 24.000000))(command "rectangle" (list 16.000000 6.000000) (list 26.000000 15.000000))(command "rectangle" (list 34.000000 14.000000) (list 55.000000 26.000000))(command "rectangle" (list 0.000000 24.000000) (list 25.000000 31.000000))(command "rectangle" (list 55.000000 14.000000) (list 73.000000 26.000000))(command "rectangle" (list 34.000000 26.000000) (list 57.000000 32.000000))(command "rectangle" (list 74.000000 25.000000) (list 88.000000 38.000000))(command "rectangle" (list 16.000000 15.000000) (list 34.000000 24.000000))(command "rectangle" (list 0.000000 31.000000) (list 21.000000 36.000000))(command "rectangle" (list 57.000000 26.000000) (list 69.000000 39.000000))(command "rectangle" (list 34.000000 32.000000) (list 55.000000 35.000000))(command "rectangle" (list 25.000000 24.000000) (list 30.000000 42.000000))(command "rectangle" (list 34.000000 35.000000) (list 50.000000 42.000000))(command "rectangle" (list 0.000000 36.000000) (list 12.000000 46.000000))(command "rectangle" (list 12.000000 36.000000) (list 24.000000 46.000000))(command "rectangle" (list 74.000000 38.000000) (list 86.000000 47.000000))(command "rectangle" (list 57.000000 39.000000) (list 73.000000 44.000000))(command "rectangle" (list 50.000000 35.000000) (list 57.000000 49.000000))(command "rectangle" (list 34.000000 42.000000) (list 50.000000 47.000000))(command "rectangle" (list 57.000000 44.000000) (list 72.000000 50.000000))(command "rectangle" (list 0.000000 46.000000) (list 18.000000 49.000000))(command "rectangle" (list 34.000000 47.000000) (list 48.000000 53.000000))(command "rectangle" (list 25.000000 42.000000) (list 31.000000 56.000000))(command "rectangle" (list 74.000000 47.000000) (list 90.000000 50.000000))(command "rectangle" (list 0.000000 49.000000) (list 14.000000 54.000000))(command "rectangle" (list 57.000000 50.000000) (list 70.000000 56.000000))(command "rectangle" (list 18.000000 46.000000) (list 25.000000 57.000000))(command "rectangle" (list 69.000000 26.000000) (list 74.000000 39.000000))(command "rectangle" (list 74.000000 50.000000) (list 83.000000 58.000000))(command "rectangle" (list 34.000000 53.000000) (list 46.000000 57.000000))(command "rectangle" (list 30.000000 24.000000) (list 33.000000 37.000000))(command "rectangle" (list 0.000000 54.000000) (list 12.000000 57.000000))(command "rectangle" (list 25.000000 56.000000) (list 34.000000 62.000000))(command "rectangle" (list 57.000000 56.000000) (list 66.000000 62.000000))(command "rectangle" (list 31.000000 42.000000) (list 34.000000 54.000000))(command "rectangle" (list 88.000000 25.000000) (list 90.000000 37.000000))(command "rectangle" (list 14.000000 49.000000) (list 18.000000 59.000000))(command "rectangle" (list 67.000000 5.000000) (list 74.000000 11.000000))(command "rectangle" (list 72.000000 44.000000) (list 74.000000 55.000000))(command "rectangle" (list 26.000000 6.000000) (list 33.000000 12.000000))(command "rectangle" (list 50.000000 49.000000) (list 55.000000 56.000000))(command "rectangle" (list 86.000000 38.000000) (list 89.000000 47.000000))(command "rectangle" (list 0.000000 57.000000) (list 9.000000 60.000000))(command "rectangle" (list 83.000000 50.000000) (list 89.000000 56.000000))(command "rectangle" (list 34.000000 57.000000) (list 44.000000 59.000000))(command "rectangle" (list 50.000000 56.000000) (list 56.000000 62.000000))(command "rectangle" (list 66.000000 56.000000) (list 73.000000 61.000000))(command "rectangle" (list 83.000000 56.000000) (list 88.000000 63.000000))(command "rectangle" (list 26.000000 12.000000) (list 34.000000 15.000000))(command "rectangle" (list 18.000000 57.000000) (list 24.000000 62.000000))(command "rectangle" (list 74.000000 58.000000) (list 83.000000 60.000000))(command "rectangle" (list 34.000000 59.000000) (list 43.000000 61.000000))(command "rectangle" (list 9.000000 57.000000) (list 14.000000 62.000000))(command "rectangle" (list 43.000000 59.000000) (list 50.000000 62.000000))(command "rectangle" (list 0.000000 60.000000) (list 7.000000 63.000000))(command "rectangle" (list 74.000000 60.000000) (list 81.000000 63.000000))(command "rectangle" (list 21.000000 31.000000) (list 24.000000 36.000000))(command "rectangle" (list 48.000000 47.000000) (list 50.000000 53.000000))(command "rectangle" (list 30.000000 37.000000) (list 34.000000 41.000000))(command "rectangle" (list 44.000000 57.000000) (list 50.000000 59.000000))(command "rectangle" (list 89.000000 0.000000) (list 90.000000 6.000000))(command "rectangle" (list 46.000000 53.000000) (list 49.000000 57.000000))(command "rectangle" (list 67.000000 11.000000) (list 70.000000 13.000000))(command "rectangle" (list 31.000000 54.000000) (list 34.000000 56.000000))(command "rectangle" (list 67.000000 13.000000) (list 70.000000 14.000000))(command "rectangle" (list 14.000000 59.000000) (list 17.000000 61.000000))(command "rectangle" (list 14.000000 61.000000) (list 17.000000 63.000000))(command "rectangle" (list 70.000000 11.000000) (list 72.000000 12.000000))(command "rectangle" (list 0 0) (list 90 90))(command "zoom" "e" ))
