(defun c:go()(command "rectangle" (list 0.000000 0.000000) (list 21.000000 13.000000))(command "rectangle" (list 21.000000 0.000000) (list 38.000000 11.000000))(command "rectangle" (list 38.000000 0.000000) (list 59.000000 5.000000))(command "rectangle" (list 38.000000 5.000000) (list 52.000000 16.000000))(command "rectangle" (list 0.000000 13.000000) (list 21.000000 16.000000))(command "rectangle" (list 0.000000 16.000000) (list 18.000000 21.000000))(command "rectangle" (list 18.000000 16.000000) (list 36.000000 21.000000))(command "rectangle" (list 38.000000 16.000000) (list 52.000000 24.000000))(command "rectangle" (list 0.000000 21.000000) (list 18.000000 25.000000))(command "rectangle" (list 52.000000 5.000000) (list 55.000000 23.000000))(command "rectangle" (list 21.000000 11.000000) (list 38.000000 14.000000))(command "rectangle" (list 18.000000 21.000000) (list 32.000000 26.000000))(command "rectangle" (list 55.000000 5.000000) (list 60.000000 19.000000))(command "rectangle" (list 38.000000 24.000000) (list 49.000000 31.000000))(command "rectangle" (list 49.000000 24.000000) (list 60.000000 28.000000))(command "rectangle" (list 21.000000 14.000000) (list 33.000000 16.000000))(command "rectangle" (list 0.000000 25.000000) (list 7.000000 31.000000))(command "rectangle" (list 32.000000 21.000000) (list 36.000000 29.000000))(command "rectangle" (list 7.000000 25.000000) (list 14.000000 30.000000))(command "rectangle" (list 14.000000 25.000000) (list 18.000000 32.000000))(command "rectangle" (list 18.000000 26.000000) (list 25.000000 29.000000))(command "rectangle" (list 55.000000 19.000000) (list 60.000000 23.000000))(command "rectangle" (list 25.000000 26.000000) (list 29.000000 31.000000))(command "rectangle" (list 49.000000 28.000000) (list 54.000000 31.000000))(command "rectangle" (list 54.000000 28.000000) (list 59.000000 31.000000))(command "rectangle" (list 36.000000 16.000000) (list 38.000000 22.000000))(command "rectangle" (list 18.000000 29.000000) (list 22.000000 32.000000))(command "rectangle" (list 29.000000 26.000000) (list 32.000000 30.000000))(command "rectangle" (list 0 0) (list 60 60))(command "zoom" "e" ))
